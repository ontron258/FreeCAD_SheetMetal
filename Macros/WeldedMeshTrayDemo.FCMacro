# -*- coding: utf-8 -*-
# Copyright 2026 Adrian
# SPDX-License-Identifier: LGPL-2.0-or-later
"""Create an editable three-flange mesh tray in a new, unsaved document."""

import FreeCAD as App
import Part
import Sketcher

from SheetMetalBaseCmd import SMBaseBend
from SheetMetalCmd import SMBendWall
from SheetMetalShapedFlangeCmd import createSheetMetalPart
from SheetMetalWeldedMeshCmd import create_welded_mesh, convert_to_editable


def create_mesh_tray_demo():
    doc = App.newDocument("WeldedMeshTray")
    doc.Label = "Welded mesh tray - flanges and cutouts"
    carrier = createSheetMetalPart(doc)
    carrier.UseMaterialCatalog = False
    carrier.Thickness = 3.7
    carrier.DefaultBendRadius = 6
    body = doc.addObject("PartDesign::Body", "SheetMetalBody")
    carrier.addObject(body)

    profile = doc.addObject("Sketcher::SketchObject", "FloorProfile")
    profile.Label = "Floor profile - 180 x 120 mm"
    body.addObject(profile)
    points = [App.Vector(0, 0, 0), App.Vector(180, 0, 0),
              App.Vector(180, 120, 0), App.Vector(0, 120, 0)]
    profile.addGeometry([Part.LineSegment(points[i], points[(i + 1) % 4])
                         for i in range(4)], False)
    for i in range(4):
        profile.addConstraint(Sketcher.Constraint("Coincident", i, 2, (i + 1) % 4, 1))
        profile.addConstraint(Sketcher.Constraint("Horizontal" if i % 2 == 0 else "Vertical", i))
    profile.addConstraint(Sketcher.Constraint("Coincident", 0, 1, -1, 1))
    width = profile.addConstraint(Sketcher.Constraint("Distance", 0, 180.0))
    depth = profile.addConstraint(Sketcher.Constraint("Distance", 1, 120.0))
    profile.renameConstraint(width, "FloorWidth")
    profile.renameConstraint(depth, "FloorDepth")

    base = body.newObject("PartDesign::FeaturePython", "CarrierBase")
    SMBaseBend(base, profile)
    base.Label = "Sheet envelope - thickness follows wire settings"
    base.Thickness = 3.7
    base.UsePartThickness = True
    base.PartDefaultsVersion = 1
    base.Radius = 6
    base.BendSide = "Outside"
    doc.recompute()
    if App.GuiUp:
        from SheetMetalBaseCmd import SMBaseViewProvider
        SMBaseViewProvider(base.ViewObject)

    source = base
    for name, axis, position, length in [
        ("BackFlange", "y", 120, 42),
        ("LeftFlange", "x", 0, 30),
        ("RightFlange", "x", 180, 30),
    ]:
        # Resolve the base perimeter geometrically rather than assuming an edge
        # number survives the preceding flange operation.
        edges = [(i, edge) for i, edge in enumerate(source.Shape.Edges)
                 if len(edge.Vertexes) == 2 and all(
                     abs(getattr(v.Point, axis) - position) < 1e-6
                     and abs(v.Point.z - carrier.Thickness.Value) < 1e-6 for v in edge.Vertexes)]
        index, _edge = max(edges, key=lambda item: item[1].Length)
        flange = body.newObject("PartDesign::FeaturePython", name)
        SMBendWall(flange, source, ["Edge" + str(index + 1)])
        flange.Label = "{} - {} mm straight leg, R6, 90 deg".format(name, length)
        flange.radius = 6
        flange.length = length
        flange.angle = 90
        flange.invert = False
        flange.gap1 = flange.gap2 = 8
        flange.BendType = "Material Outside"
        flange.LengthSpec = "Leg"
        doc.recompute()
        if App.GuiUp:
            from SheetMetalCmd import SMViewProviderTree
            SMViewProviderTree(flange.ViewObject)
        source = flange

    def rectangle(x, y, width, height):
        p = [App.Vector(x, y, 0), App.Vector(x + width, y, 0),
             App.Vector(x + width, y + height, 0), App.Vector(x, y + height, 0)]
        return [Part.LineSegment(p[i], p[(i + 1) % 4]) for i in range(4)]

    cuts = [
        ("FloorWindow", rectangle(85, 40, 60, 30)),
        ("RoundOpening", [Part.Circle(App.Vector(36, 55, 0), App.Vector(0, 0, 1), 12)]),
        ("FrontNotch", rectangle(110, -5, 28, 19)),
        ("HandleSlot", rectangle(65, -36, 50, 14)),
    ]
    for name, geometry in cuts:
        sketch = body.newObject("Sketcher::SketchObject", name + "Profile")
        sketch.addGeometry(geometry, False)
        if name == "HandleSlot":
            sketch.Placement = App.Placement(App.Vector(0, 140, 0), App.Rotation(App.Vector(1, 0, 0), -90))
        else:
            sketch.setExpression("Placement.Base.z", base.Name + ".Thickness")
        cut = body.newObject("PartDesign::Pocket", name)
        cut.Profile = sketch
        cut.Type = 1  # Through all, including after an envelope-thickness change.
        cut.Refine = True
        doc.recompute()
        source = cut
    source.Label = "Handle slot - finished sheet envelope"
    body.Tip = source
    carrier.Tip = source.Name
    if not source.Shape.isValid() or len(source.Shape.Solids) != 1:
        raise ValueError("The demonstration carrier must be one valid solid.")

    candidates = [i for i, face in enumerate(source.Shape.Faces)
                  if isinstance(face.Surface, Part.Plane) and face.normalAt(0, 0).z > 0.9]
    root = max(candidates, key=lambda i: source.Shape.Faces[i].Area)
    part, mesh = create_welded_mesh(
        doc, source, "Face" + str(root + 1), LongitudeDiameter=2,
        LongitudePitch=10, LatitudePitch=10, WeldPenetration=0.3, KFactor=0.5,
    )
    part.Label = "Welded mesh tray - 2 mm wire, 10 mm pitch"
    longitude, latitude = convert_to_editable(mesh)
    # Demonstrate a local trim, leaving the remaining generated wire layout intact.
    longest = max(range(longitude.GeometryCount),
                  key=lambda i: longitude.Geometry[i].length())
    line = longitude.Geometry[longest]
    direction = line.EndPoint - line.StartPoint
    direction.normalize()
    longitude.delGeometry(longest)
    longitude.addGeometry(Part.LineSegment(line.StartPoint + direction * 4, line.EndPoint), False)
    part.addProperty("App::PropertyStringList", "DemoNotes", "Example")
    part.DemoNotes = [
        "180 x 120 mm floor; back straight leg 42 mm; side straight legs 30 mm; R6 bends.",
        "Carrier cuts: 60 x 30 floor window, diameter 24 hole, 28 x 14 front notch, 50 x 14 back handle.",
        "2 mm wire, initial 10 mm pitch, 0.3 mm weld penetration gives a 3.7 mm welded envelope.",
        "Both wire sketches are editable. One longitude wire has been shortened by 4 mm at one end.",
        "Toggle Flat Pattern Workspace to inspect the preparation; double-click a wire sketch to edit it.",
        "Pitch/count apply after Regenerate wire pattern on Formed Wires; undo restores edits.",
        "The single Body holds the editable flanges and pockets; its 3.7 mm thickness is the wire envelope.",
        "Carrier allowance is geometric. Flat and formed wire lengths can differ around bends.",
    ]
    doc.recompute()
    if mesh.LastError or not mesh.Shape.isValid() or not mesh.FlatShape.isValid():
        raise ValueError(mesh.LastError or "Invalid demonstration wire geometry.")

    if App.GuiUp:
        import FreeCADGui as Gui
        for obj in doc.Objects:
            obj.ViewObject.Visibility = False
        part.ViewObject.Visibility = True
        mesh.ViewObject.Visibility = True
        mesh.ViewObject.ShapeColor = (0.70, 0.74, 0.80)
        mesh.ViewObject.LineColor = (0.20, 0.24, 0.30)
        mesh.ViewObject.DisplayMode = "Flat Lines"
        Gui.activeDocument().activeView().viewAxonometric()
        Gui.activeDocument().activeView().fitAll()
    return doc, part, mesh


mesh_tray_doc, mesh_tray_part, mesh_tray_formed = create_mesh_tray_demo()
